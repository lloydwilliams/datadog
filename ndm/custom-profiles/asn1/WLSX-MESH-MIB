--- ArubaOS 6.5.4.19_79367
-- vim:set ts=4 sw=4:
WLSX-MESH-MIB DEFINITIONS ::= BEGIN

   IMPORTS
       TEXTUAL-CONVENTION FROM SNMPv2-TC 
              
       MODULE-IDENTITY,
       OBJECT-TYPE,
       snmpModules,
       Integer32,
       Unsigned32,
	   Counter32,
	   IpAddress,
	   NOTIFICATION-TYPE
           FROM SNMPv2-SMI

       TDomain,
       DisplayString,
       PhysAddress,
       TAddress,
       TimeInterval,
       RowStatus,
       StorageType,
       TestAndIncr,
       DateAndTime,
	   MacAddress,
	   TruthValue
           FROM SNMPv2-TC
           
       ArubaMeshRole,
	   ArubaEncryptionMethods,
	   ArubaPhyType
	   		FROM ARUBA-TC
	   wlanAPMacAddress
           FROM WLSX-WLAN-MIB
       OBJECT-GROUP
           FROM SNMPv2-CONF
		wlsxEnterpriseMibModules
			FROM ARUBA-MIB;

   wlsxMeshMIB MODULE-IDENTITY 
       LAST-UPDATED "0708060518Z"
       ORGANIZATION "Aruba Wireless Networks"
       CONTACT-INFO
            "Postal:    1322 Crossman Avenue
                        Sunnyvale, CA 94089	
            E-mail:     dl-support@arubanetworks.com
            Phone:      +1 408 227 4500"
       DESCRIPTION
           "This MIB module defines MIB objects which provides
            information about Mesh portal and topology 
		in the Aruba controller."
       REVISION        "0708060518Z"
       DESCRIPTION
           "The initial revision."
       ::= { wlsxEnterpriseMibModules 13 }

   wlsxMeshInfoGroup			OBJECT IDENTIFIER ::= { wlsxMeshMIB 1 }
   
   wlsxMeshNodeGroup           OBJECT IDENTIFIER ::= { wlsxMeshInfoGroup 1 }

   wlsxMeshNodeTotal     OBJECT-TYPE
         SYNTAX       Unsigned32
         MAX-ACCESS   read-only
         STATUS       current
         DESCRIPTION
            "
			Total Number of mesh nodes in the controller.
            "
        ::= { wlsxMeshNodeGroup 1 }

   wlsxMeshNodeTable  OBJECT-TYPE 
	  SYNTAX       SEQUENCE OF MeshEntry
	  MAX-ACCESS   not-accessible		
      STATUS       current 
      DESCRIPTION 
	  	"
			This table lists Mesh Node Info. 
		"
      ::= { wlsxMeshNodeGroup 2 } 
      
   wlsxMeshNodeEntry OBJECT-TYPE
	  SYNTAX       MeshEntry 
	  MAX-ACCESS   not-accessible		
      STATUS       current 
      DESCRIPTION 
             ""
	  INDEX {wlanAPMacAddress}
      ::= { wlsxMeshNodeTable 1 } 
      
   MeshEntry ::=
     SEQUENCE {
		wlsxMeshRole                    ArubaMeshRole,
		wlsxMeshNodeParent              MacAddress,
		wlsxMeshNodeChildrenCount       Unsigned32,
		wlsxMeshNodeCluster             DisplayString,
		wlsxMeshNodeRfBand              ArubaPhyType,
		wlsxMeshNodePathCost            Integer32,
		wlsxMeshNodeNodeCost            Integer32,
		wlsxMeshNodeLinkCost            Integer32,
		wlsxMeshNodeHopCount            Integer32,
                wlsxMeshSNR                     Unsigned32,
                wlsxMeshTxRate                  Unsigned32,
                wlsxMeshRxRate                  Unsigned32,
                wlsxMeshUplinkAge               TimeTicks,
                wlsxMeshNumRecoveryChildren     Unsigned32,
                wlsxMeshTopologyUpdateAge       TimeTicks,
                wlsxMeshIsRecovery              TruthValue,
                wlsxMeshIs11n                   TruthValue
    } 
	wlsxMeshRole OBJECT-TYPE
         SYNTAX       ArubaMeshRole
         MAX-ACCESS   read-write
         STATUS       current
         DESCRIPTION
            "
			Mesh role
            "
        ::= { wlsxMeshNodeEntry 1 }
        
 	wlsxMeshNodeParent OBJECT-TYPE
         SYNTAX       MacAddress
  		 MAX-ACCESS   read-only		
         STATUS       current
         DESCRIPTION
            "
			Wired MAC address of mesh node's parent
            "
        ::= { wlsxMeshNodeEntry 2 }

	wlsxMeshNodeChildrenCount OBJECT-TYPE
         SYNTAX       Unsigned32
  		 MAX-ACCESS   read-only		
         STATUS       current
         DESCRIPTION
            "
			Mesh node children count
            "
        ::= { wlsxMeshNodeEntry 3 }

    wlsxMeshNodeCluster OBJECT-TYPE
         SYNTAX       DisplayString(SIZE(0..64))
  		 MAX-ACCESS   read-only		
         STATUS       current
         DESCRIPTION
            "
			Mesh cluster name.
            "
        ::= { wlsxMeshNodeEntry 4 }

	wlsxMeshNodeRfBand OBJECT-TYPE
         SYNTAX       ArubaPhyType
  		 MAX-ACCESS   read-only		
         STATUS       current
         DESCRIPTION
            "
			Mesh node rf band
            "
        ::= { wlsxMeshNodeEntry 5 }

	wlsxMeshNodePathCost OBJECT-TYPE
         SYNTAX       Integer32
  		 MAX-ACCESS   read-only		
         STATUS       current
         DESCRIPTION
            "
			Mesh topology path cost
            "
        ::= { wlsxMeshNodeEntry 6 }
 
	wlsxMeshNodeNodeCost OBJECT-TYPE
         SYNTAX       Integer32
  		 MAX-ACCESS   read-only		
         STATUS       current
         DESCRIPTION
            "
			Mesh topology node cost
            "
        ::= { wlsxMeshNodeEntry 7 }

 	wlsxMeshNodeLinkCost OBJECT-TYPE
         SYNTAX       Integer32
  		 MAX-ACCESS   read-only		
         STATUS       current
         DESCRIPTION
            "
			Mesh topology link cost
            "
        ::= { wlsxMeshNodeEntry 8 }

  	wlsxMeshNodeHopCount OBJECT-TYPE
         SYNTAX       Integer32
  		 MAX-ACCESS   read-only		
         STATUS       current
         DESCRIPTION
            "
			Mesh topology hop count.
            "
        ::= { wlsxMeshNodeEntry 9 }

  	wlsxMeshSNR OBJECT-TYPE
         SYNTAX       Unsigned32
  		 MAX-ACCESS   read-only		
         STATUS       current
         DESCRIPTION
            "
			Signal-to-noise ratio mesh point sees its parent at. 
            "
        ::= { wlsxMeshNodeEntry 10 }

  	wlsxMeshTxRate OBJECT-TYPE
         SYNTAX       Unsigned32
  		 MAX-ACCESS   read-only		
         STATUS       current
         DESCRIPTION
            "
			Transmit rate for mesh-uplink [mbps].
            "
        ::= { wlsxMeshNodeEntry 11 }

  	wlsxMeshRxRate OBJECT-TYPE
         SYNTAX       Unsigned32
  		 MAX-ACCESS   read-only		
         STATUS       current
         DESCRIPTION
            "
			Receive rate for mesh-uplink [mbps].
            "
        ::= { wlsxMeshNodeEntry 12 }

  	wlsxMeshUplinkAge OBJECT-TYPE
         SYNTAX       TimeTicks
  		 MAX-ACCESS   read-only		
         STATUS       current
         DESCRIPTION
            "
			Time elapsed since the mesh-uplink was formed.
            "
        ::= { wlsxMeshNodeEntry 13 }

  	wlsxMeshNumRecoveryChildren OBJECT-TYPE
         SYNTAX       Unsigned32
  		 MAX-ACCESS   read-only		
         STATUS       current
         DESCRIPTION
            "
			The number of children in recovery this mesh node has.
            "
        ::= { wlsxMeshNodeEntry 14 }

  	wlsxMeshTopologyUpdateAge OBJECT-TYPE
         SYNTAX       TimeTicks
  		 MAX-ACCESS   read-only		
         STATUS       current
         DESCRIPTION
            "
			Time elapsed since the last mesh topology update was received from this node.
            "
        ::= { wlsxMeshNodeEntry 15 }

  	wlsxMeshIsRecovery OBJECT-TYPE
         SYNTAX       TruthValue
  		 MAX-ACCESS   read-only		
         STATUS       current
         DESCRIPTION
            "
			True if this mesh point is in recovery.
            "
        ::= { wlsxMeshNodeEntry 16 }

  	wlsxMeshIs11n OBJECT-TYPE
         SYNTAX       TruthValue
  		 MAX-ACCESS   read-only		
         STATUS       current
         DESCRIPTION
            "
			True if this mesh node is 11n-enabled.
            "
        ::= { wlsxMeshNodeEntry 17 }

END
